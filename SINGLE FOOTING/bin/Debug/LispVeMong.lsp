(command "NETLOAD" "J:/APP/DOTNET 10/PECC/SINGLE FOOTING/SINGLE FOOTING/SINGLE FOOTING/bin/Debug/SINGLE FOOTING.dll")
(command "NETLOAD" "J:/APP/DOTNET 10/PECC/SINGLE FOOTING/SINGLE FOOTING/SINGLE FOOTING/bin/Debug/Microsoft.Xaml.Behaviors.dll")
